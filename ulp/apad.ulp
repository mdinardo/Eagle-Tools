#usage "<b>Create a PTH pad with an anchor point (x1, y1) at the edge of the hole and center point (cx, cy)</b>\n"
"<p>"
"Syntax:  arect [R] x1 y1 [cx cy]"
"<p>"
"Width and height are mandatory parameters."
"<p>"
"Include the R flag to make all coordinates relative to the mark."
"<p>"
"The center coordinate may be omitted; it will default to (0 0) (or (R0 0) if the relative flag is set)."
"<p>"
"Example: rectangle with anchor point at (1 2), center at default (0 0):   acir 1 2"
"<p>"
"Example: rectangle relative to mark, with anchor point at (R3 4) centered at (R5 6): acir R 3 4 5 6"


//output("/tmp/ulp_output.txt") {
    
    real x1 = 0, y1 = 0;
    real cx = 0, cy = 0;
    real diammeter = 0;

    //dimension index, position index
    int d_index = 0, p_index = 0;
    int relative = 0;

    // Relative flag set
    if (argc == 4 || argc == 6) {
        int res = strstr("R", strupr(argv[1]));
        if (-1 != res) {relative = 1;}
        else {
            string s = "";
            sprintf(s, "Invalid parameter: %s", argv[1]);
	  dlgMessageBox(s);
            exit(1);
        }
        
        d_index = 2;
        
        if (argc == 6) {
            p_index = 4;
        }
    }
    
    else if (argc == 3 || argc == 5) {
        d_index = 1;

        if (argc == 5) {
            p_index = 3;
        }
    }

    else {
        dlgMessageBox("Incorrect number of arguments","Ok");
        exit(1);
    }

    x1 = strtod(argv[d_index]);
    y1 = strtod(argv[d_index + 1]);

    if (p_index) {
        cx = strtod(argv[p_index]);
        cy = strtod(argv[p_index + 1]);
    }

    real dx = (cx - x1);    
    real dy = (cy - y1);

    diammeter = 2.0 * sqrt(dx*dx + dy * dy);

    string s = "";
    string fmt = "";
    if (relative) {
        fmt = "PAD %f (R%f %f);";
    }
    else {
        fmt = "PAD %f (%f %f);";
    }
    sprintf(s, fmt,        
        diammeter,
        cx, cy

    );
    exit(s);
//}
