#usage "<b>Create a circle of diammeter d with center point (cx, cy)</b>\n"
"<p>"
"Syntax:  ccir [R] d [cx cy]"
"<p>"
"Diammeter is a mandatory parameter."
"<p>"
"Include the R flag to make all coordinates relative to the mark."
"<p>"
"The center coordinate may be omitted; it will default to (0 0) (or (R0 0) if the relative flag is set)."
"<p>"
"Example: circle with diammeter 2, center at default (0 0):   dcir 2"
"<p>"
"Example: circle relative to mark, with diammeter 3, centered at (R5 6):  dcir R 3 5 6"


//output("/tmp/ulp_output.txt") {
    
    real d = 0;
    real cx = 0, cy = 0;

    //diammeter index, center position index
    int d_index = 0, c_index = 0;
    int relative = 0;

    // Relative flag set
    if (argc == 3 || argc == 5) {
        int res = strstr("R", strupr(argv[1]));
        if (-1 != res) {relative = 1;}
        else {
            string s = "";
            sprintf(s, "Invalid parameter: %s", argv[1]);
	  dlgMessageBox(s);
            exit(1);
        }
        
        d_index = 2;
        
        if (argc == 5) {
            c_index = 3;
        }
    }
    
    else if (argc == 2 || argc == 4) {
        d_index = 1;

        if (argc == 4) {
            c_index = 2;
        }
    }

    else {
        dlgMessageBox("Incorrect number of arguments","Ok");
        exit(1);
    }

    d = strtod(argv[d_index]);
    
    if (c_index) {
        cx = strtod(argv[c_index]);
        cy = strtod(argv[c_index + 1]);
    }


    string s = "";
    string fmt = "";
    if (relative) {
        fmt = "CIRCLE (R%f %f) (R%f %f);";
    }
    else {
        fmt = "CIRCLE (%f %f) (%f %f);";
    }
    sprintf(s, fmt,        
        cx, cy,
        (cx + d/2.0), cy
    );
    exit(s);
//}
