//SOURCE: reflowster.com/blog/2015/01/14/yourfirstulp.html
//Modified to create a rectangle instead of a wire box, and to include support for relative coordinates.

#usage "<b>Create a rectangle centered at (x, y)</b>\n"
"<p>"
"Syntax:  crect [R] w h [x y]"
"<p>"
"Width and height are mandatory parameters."
"<p>"
"Include the R flag to make all coordinates relative to the mark."
"<p>"
"The center coordinate may be omitted; it will default to (0 0) (or (R0 0) if the relative flag is set)."
"<p>"
"Example: rectangle with (width height) of (1 2):   crect 1 2"
"<p>"
"Example: rectangle with (width height) of (3 4) centered at (5 6):  crect 3 4 5 6"


//output("/tmp/ulp_output.txt") {
    
    real width = 0, height = 0;
    real x = 0, y = 0;

    //dimension index, position index
    int d_index = 0, p_index = 0;
    int relative = 0;

    // Relative flag set
    if (argc == 4 || argc == 6) {
        int res = strstr("R", strupr(argv[1]));
        if (-1 != res) {relative = 1;}
        else {
            string s = "";
            sprintf(s, "Invalid parameter: %s", argv[1]);
	  dlgMessageBox(s);
            exit(1);
        }
        
        d_index = 2;
        
        if (argc == 6) {
            p_index = 4;
        }
    }
    
    else if (argc == 3 || argc == 5) {
        d_index = 1;

        if (argc == 5) {
            p_index = 3;
        }
    }

    else {
        dlgMessageBox("Incorrect number of arguments","Ok");
        exit(1);
    }

    width = strtod(argv[d_index]);
    height = strtod(argv[d_index + 1]);

    if (p_index) {
        x = strtod(argv[p_index]);
        y = strtod(argv[p_index + 1]);
    }

    string s = "";
    string fmt = "";
    if (relative) {
        fmt = "RECT (R%f %f) (R%f %f);";
    }
    else {
        fmt = "RECT (%f %f) (%f %f);";
    }
    sprintf(s, fmt,        
        x-width/2.0,y-height/2.0,
        x+width/2.0,y+height/2.0

    );
    exit(s);
//}
