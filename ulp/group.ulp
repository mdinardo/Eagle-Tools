#usage "<b>Synchronizes a group between the board and schematic</b>\n"
"<p>"
"The names of the parts in the 'Source' window which have their group flag set are recorded.<br>"
"Then for the 'Target' window, the group flag is set on parts if their name was recorded."
"<p>"
"This script can operate in two modes: Source Push, and Target Pull."
"<p>"
"Source Push mode will use the group that is defined in the current (Source) window to define the group in the other (Target) window.<br>"
"Target Pull mode will use the group that is defined in the other (Source) window to define the group in the current (Target) window.<br>"
"<p>"
"By default, the script runs in Source Push mode.<br>"
"To operate in Target Pull mode, use the 'E' flag.<br>"
"<p>"

"Flags:<br>"
"    E - Use the 'External' group; Run in Target Pull mode."
"<p>"
"Usage Table:<br>"
"<table border = '1' cellpadding='5'>"
"<tr><td>Current Window</td><td>Source Window</td><td>Target Window</td><td>CLI Flags</td></tr>"
"<tr><td>Board</td><td>Board</td><td>Schematic</td><td></td></tr>"
"<tr><td>Board</td><td>Schematic</td><td>Board</td><td>E</td></tr>"
"<tr><td>Schematic</td><td>Schematic</td><td>Board</td><td></td></tr>"
"<tr><td>Schematic</td><td>Board</td><td>Schematic</td><td>E</td></tr>"
"</table>"

#include "bool.ulp"

int name_count = 0;
string names[];

// CLI flags
string CLI_FLAG_EXTERNAL = "E";
string CLI_FLAG_CLEAR = "C";

int is_external = FALSE;
int do_group_clear = FALSE;

//populates the names array with the names of parts that are grouped in the schematic S.
void sch_populate_names(UL_SCHEMATIC S) {
    S.parts(P) {
        P.instances(I) {
            if (ingroup(I)){
                names[name_count++] = P.name;
            }
        }
    }
}

//populates the names array with the names of parts that are grouped in the board B.
void brd_populate_names(UL_BOARD B) {
    B.elements(E) {
        if (ingroup(E)) {
            names[name_count++] = E.name;
        }
    }
    
}

// checks if the string 'name' is in the names array.
int is_name_recorded(string name) {
    for (int i = 0; i < name_count; i++) {
        if (name == names[i]) return TRUE;
    }
    return FALSE;
}

//Removes everything from schematic S's group.
void sch_clr_group_all(UL_SCHEMATIC S) {
    clrgroup(S);
}

//Removes everything from board B's group.
void brd_clr_group_all(UL_BOARD B) {
    clrgroup(B);
}

//Removes all part instances from a schematic's group
void sch_clr_group_instances(UL_SCHEMATIC S) {
    S.parts(P) {
        P.instances(I) {
            clrgroup(I);
        }
    }
}

//Removes all elements from a board's group
void brd_clr_group_elements(UL_BOARD B) {
    B.elements(E) {
        clrgroup(E);
    }
}

//Sets the group flag for parts in schematic S
void sch_set_group(UL_SCHEMATIC S) {
    S.parts(P) {
        P.instances(I) {
            if (is_name_recorded(I.name)){
                setgroup(I);
            }
        }
    }
}

//Sets the group flag for elements in board B
void brd_set_group(UL_BOARD B) {
    B.elements(E) {
        if (is_name_recorded(E.name)) {
            setgroup(E);
        }
    }
}

int parse_cli_args() {
	
	
	if (argc == 2 && "E" == strupr(argv[1])) {
		is_external = TRUE;
	}

	int i;
	for (i = 2; i < argc; i++) {
		string arg_upr = strupr(argv[1]);
		
		if (arg_upr == CLI_FLAG_EXTERNAL) {
			is_external = TRUE;
		}
		else if (arg_upr == CLI_FLAG_CLEAR) {
			do_group_clear = TRUE;
		}
	}

	return 0;
}

output ("ulp_group.test") {
    UL_SCHEMATIC S;
    UL_BOARD B;
    int ret;
	
	ret = parse_cli_args();
	if (0 != ret) {
		// error out
	}

    //Current window is schematic.
    if (schematic) schematic(SCH) {
        project.board(BRD) {
            //Set schematic group with group from board.
            if (is_external) {
                brd_populate_names(BRD);
				if (do_group_clear) sch_clr_group_all(SCH);
				sch_set_group(SCH);

            }
            //Set board group with group from schematic.
            else {
                sch_populate_names(SCH);
				if (do_group_clear) brd_clr_group_all(BRD);
                brd_set_group(BRD);
            }
        }
    }
    
    //Current window is board.
    if (board) board(BRD) {
        project.schematic(SCH) {
            //Set board group with group from schematic.
            if (is_external) {
                sch_populate_names(SCH);
				if (do_group_clear) brd_clr_group_all(BRD);
                brd_set_group(BRD);
            }
            //Set schematic group with group from board.
            else {
                brd_populate_names(BRD);
				if (do_group_clear) sch_clr_group_all(SCH);
                sch_set_group(SCH);
            }
        }
    }

    for(int i = 0; i < name_count; i++) {
        printf("%s\n", names[i]);
    }
}
