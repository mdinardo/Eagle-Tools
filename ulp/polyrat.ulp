#usage "<b>Enables and disables net polygon filling upon the use of the ratsnest tool.</b>\n"

string ScriptName = "polyrat";
string Version = "1.00";

string command = "";
string mode = "";

// Lets you type on/off, or 1/0
mode = argv[1];
if (mode == "1") mode = "on";
if (mode == "0") mode = "off";


sprintf(command, "set POLYGON_RATSNEST %s", mode);
exit(command);
